;; Load engine/scripts/replace_frames.lsp, then this file.
;; Run CFRSCALETEST. Only in-memory DXF lists are used; no drawing changes.
(defun cfrt:check (label actual expected / ok)
  (setq ok (equal actual expected 0.000001))
  (if ok
    (setq cfrt:passed (1+ cfrt:passed))
    (setq cfrt:failed (1+ cfrt:failed)))
  (princ (strcat "\n" (if ok "PASS " "FAIL ") label))
  (if (not ok)
    (princ (strcat " actual=" (vl-princ-to-string actual)
                   " expected=" (vl-princ-to-string expected)))))

(defun cfrt:embedded (data / active out item)
  (setq active nil out '())
  (foreach item data
    (if (and (= (car item) 101) (= (cdr item) "Embedded Object"))
      (setq active T)
      (if active (setq out (cons item out)))))
  (reverse out))

(defun c:CFRSCALETEST (/ fixture result embedded)
  (setq cfrt:passed 0 cfrt:failed 0)
  (setq fixture
    '((0 . "ATTRIB") (2 . "图名") (10 12.0 34.0 0.0)
      (11 13.0 35.0 0.0) (50 . 0.75) (40 . 200.0) (41 . 0.8)
      (1 . "old") (101 . "Embedded Object") (10 13.0 35.0 0.0)
      (40 . 200.0) (41 . 3250.0) (1 . "old")))
  (setq result (fra:fit-overlay-attribute fixture "A-W-ST001" 18.0 2.4 1.2 1.0 1.0))
  (cfrt:check "1x drawing number" (fra:get 40 result) 2.4)
  (setq result (fra:fit-overlay-attribute fixture "A-W-ST001" 18.0 2.4 1.2 50.0 50.0))
  (cfrt:check "50x drawing number" (fra:get 40 result) 120.0)
  (setq result (fra:fit-overlay-attribute fixture "ABCDEFGHIJKLMNOP" 66.0 4.0 1.2 50.0 50.0))
  (cfrt:check "50x drawing name" (fra:get 40 result) 200.0)
  (setq embedded (cfrt:embedded result))
  (cfrt:check "embedded height matches outer" (fra:get 40 embedded) 200.0)
  (cfrt:check "embedded cell width preserved" (fra:get 41 embedded) 3250.0)
  (cfrt:check "insertion point preserved" (fra:get 10 result) (fra:get 10 fixture))
  (cfrt:check "alignment point preserved" (fra:get 11 result) (fra:get 11 fixture))
  (cfrt:check "rotation preserved" (fra:get 50 result) 0.75)
  (setq result (fra:fit-overlay-attribute fixture "A-W-ST001" 18.0 2.4 1.2 0.5 0.5))
  (cfrt:check "0.5x drawing number" (fra:get 40 result) 1.2)
  (setq result (fra:fit-overlay-attribute fixture "A-W-ST001" 18.0 2.4 1.2 100.0 50.0))
  (cfrt:check "nonuniform height" (fra:get 40 result) 120.0)
  (cfrt:check "nonuniform width factor" (fra:get 41 result) 1.6)
  (cfrt:check "nonuniform embedded width override"
    (atof (substr (fra:get 1 (cfrt:embedded result)) 3)) 1.6)
  (setq result (fra:fit-overlay-attribute fixture "A-W-ST001" 18.0 2.4 1.2 -50.0 50.0))
  (cfrt:check "mirrored scale keeps positive height" (fra:get 40 result) 120.0)
  (cfrt:check "mirrored scale keeps positive width factor" (fra:get 41 result) 0.8)
  (setq result (fra:fit-overlay-attribute fixture
    "AAAAAAAAAAAAAAAAAAAAAAAAAAAAAAAAAAAAAAAAAAAAAAAAAAAAAAAAAAAAAAAAAAAAAAAAAAAAAAAAAAAAAAAAAAAAAAAAAAAA"
    66.0 4.0 1.2 50.0 50.0))
  (cfrt:check "long value scaled minimum height" (fra:get 40 result) 60.0)
  (cfrt:check "long value width compression" (fra:get 41 result) 0.55)
  (princ (strcat "\nCFR_SCALE_TEST_COMPLETE|passed=" (itoa cfrt:passed)
                 "|failed=" (itoa cfrt:failed)))
  (princ))
(princ "\nScale regression loaded. Run CFRSCALETEST after loading replace_frames.lsp.")
(princ)

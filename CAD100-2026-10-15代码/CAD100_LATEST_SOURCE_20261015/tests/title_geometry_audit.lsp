;; Read-only diagnostic: top-level local INSERT attributes in every layout.
;; Run CAD100TITLEAUDIT once in the original DWG and once in the output DWG.
(vl-load-com)
(defun ctg:s (value / out number)
  (cond
    ((numberp value) (rtos value 2 12))
    ((and (listp value) (numberp (car value)))
      (setq out "(")
      (foreach number value
        (setq out (strcat out (if (= out "(") "" " ") (rtos number 2 12))))
      (strcat out ")"))
    (value (vl-princ-to-string value))
    (T "nil")))
(defun ctg:write (label value)
  (write-line (strcat label "=" (ctg:s value)) ctg:file))
(defun ctg:attributes (insert / current data result)
  (setq current (entnext insert) result '())
  (while current
    (setq data (entget current))
    (cond
      ((= (cdr (assoc 0 data)) "SEQEND") (setq current nil))
      ((= (cdr (assoc 0 data)) "ATTRIB")
        (if (member (cdr (assoc 2 data)) '("图名" "图号"))
          (setq result (cons data result)))
        (setq current (entnext current)))
      (T (setq current (entnext current)))))
  (reverse result))
(defun c:CAD100TITLEAUDIT (/ *error* path selected index insert data attributes attr style count)
  (defun *error* (message)
    (if ctg:file
      (progn (write-line (strcat "AUDIT_ERROR=" message) ctg:file)
        (close ctg:file) (setq ctg:file nil)))
    (princ (strcat "\nAudit stopped: " message)) (princ))
  (setq ctg:file nil)
  (setq path (strcat (getvar "DWGPREFIX")
    (vl-filename-base (getvar "DWGNAME")) "_title_geometry_audit.txt"))
  (setq ctg:file (open path "w"))
  (if ctg:file
    (progn
      (write-line "CAD100_TITLE_GEOMETRY_AUDIT|FORMAT=1" ctg:file)
      (ctg:write "DRAWING" (strcat (getvar "DWGPREFIX") (getvar "DWGNAME")))
      (ctg:write "SCOPE" "Top-level local INSERT attributes; all layouts; no drawing edits")
      (setq selected (ssget "_X" '((0 . "INSERT"))) index 0 count 0)
      (if selected
        (repeat (sslength selected)
          (setq insert (ssname selected index) index (1+ index))
          (setq attributes (ctg:attributes insert))
          (if attributes
            (progn
              (setq data (entget insert))
              (write-line "BEGIN_TITLE" ctg:file)
              (ctg:write "BLOCK" (cdr (assoc 2 data)))
              (ctg:write "LAYOUT" (cdr (assoc 410 data)))
              (ctg:write "INSERT_DXF" data)
              (foreach attr attributes
                (setq count (1+ count))
                (write-line "BEGIN_ATTRIBUTE" ctg:file)
                (ctg:write "TAG" (cdr (assoc 2 attr)))
                (ctg:write "TEXT" (cdr (assoc 1 attr)))
                (ctg:write "HEIGHT" (cdr (assoc 40 attr)))
                (ctg:write "WIDTH_FACTOR" (cdr (assoc 41 attr)))
                (ctg:write "INSERTION_POINT" (cdr (assoc 10 attr)))
                (ctg:write "ALIGNMENT_POINT" (cdr (assoc 11 attr)))
                (ctg:write "HORIZONTAL_MODE" (cdr (assoc 72 attr)))
                (ctg:write "VERTICAL_MODE" (cdr (assoc 74 attr)))
                (ctg:write "ROTATION" (cdr (assoc 50 attr)))
                (ctg:write "TEXT_STYLE" (cdr (assoc 7 attr)))
                (setq style (tblsearch "STYLE" (cdr (assoc 7 attr))))
                (ctg:write "STYLE_DXF" style)
                ;; Includes repeated codes and embedded MTEXT formatting.
                (ctg:write "ATTRIBUTE_DXF" attr)
                (write-line "END_ATTRIBUTE" ctg:file))
              (write-line "END_TITLE" ctg:file)))))
      (ctg:write "ATTRIBUTE_COUNT" count)
      (write-line "AUDIT_COMPLETE=T" ctg:file)
      (close ctg:file) (setq ctg:file nil)
      (princ (strcat "\nAudit saved: " path))
      (if (= count 0) (princ "\nNo matching local attributes; this report cannot verify the visible title.")))
    (princ "\nCannot create audit file in the drawing folder."))
  (princ))
(princ "\nLoaded. Run CAD100TITLEAUDIT. No drawing edits are performed.")
(princ)
